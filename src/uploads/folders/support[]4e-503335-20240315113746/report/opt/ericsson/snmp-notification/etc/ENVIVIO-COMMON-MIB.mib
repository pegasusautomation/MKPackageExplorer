--
-- ENVIVIO-COMMON-MIB.mib
--

	ENVIVIO-COMMON-MIB DEFINITIONS ::= BEGIN

		IMPORTS
			enterprises, TimeTicks, IpAddress, Unsigned32, Gauge32,
			OBJECT-TYPE, NOTIFICATION-TYPE, MODULE-IDENTITY
				FROM SNMPv2-SMI
			TEXTUAL-CONVENTION
				FROM SNMPv2-TC
			OBJECT-GROUP, NOTIFICATION-GROUP
				FROM SNMPv2-CONF;


--  Structure of the Envivio common MIB tree
--
		-- 1.3.6.1.4.1.10613
		envivio MODULE-IDENTITY
			LAST-UPDATED "202204270000Z"		-- April 27, 2022 at 00:00 GMT
			ORGANIZATION
				"Mediakind"
			CONTACT-INFO
				"www.mediakind.com"
			DESCRIPTION
				"Structure of the Envivio common MIB tree"
			REVISION "200410180000Z"		-- October 18, 2004 at 00:00 GMT
			DESCRIPTION
				"Version 2.11"
			REVISION "200710050000Z"		-- October 5, 2007 at 00:00 GMT
			DESCRIPTION
				"Modified Trap notifications for Rosa compatibility"
			REVISION "200712170000Z"		-- December 17, 2007 at 00:00 GMT
			DESCRIPTION
				"Added OID for 4Stream"
			REVISION "200801210000Z"		-- January 21, 2008 at 00:00 GMT
			DESCRIPTION
				"Enhanced Trap definition for compatibility with CastelRock SNMP"
			REVISION "201002030000Z"		-- February 3, 2010 at 00:00 GMT
			DESCRIPTION
				"Added OID for 4Balancer"
			REVISION "201008030000Z"		-- August 3, 2010 at 00:00 GMT
			DESCRIPTION
				"Fix warning in trap definition"
			REVISION "201206120000Z"		-- June 12, 2012 at 00:00 GMT
			DESCRIPTION
				"Added OID for Performances Monitoring"
			REVISION "201304030000Z"		-- April 3, 2013 at 00:00 GMT
			DESCRIPTION
				"Update object class definitions (CR device auto discovery)"
			REVISION "201702220000Z"		-- February 22, 2017 at 00:00 GMT
			DESCRIPTION
				"remove all OIDs not supported by the SNMP microservice"
			REVISION "201802030000Z"		-- February 3, 2018 at 00:00 GMT
			DESCRIPTION
				"Added trapAlarmNotification2. Added ericssonMFMmS option to TcObjectClass. Added NOTIFICATION-GROUP and OBJECT-GROUP entries."
			REVISION "202204270000Z"		-- April 27, 2022 at 00:00 GMT
			DESCRIPTION
				"Added ServerIp field to trap"

			::= { enterprises 10613 }


--
-- Textual conventions
--

		TcObjectClass ::= TEXTUAL-CONVENTION
			STATUS current
			DESCRIPTION
				"Identifier indicating the class of the equipment:
				- indeterminate (0)
				- envivioCommon (1)
				- envivioMuseLive (2)
				- obsolete1 (3)
				- obsolete2 (4)
				- envivio4Manager (5)
				- obsolete3 (6)
				- obsolete4 (7)
				- obsolete5 (8)
				- envivio4Balancer (9)
				- envivioHalo (10)
				- envivioMuseOnDemand (11)
				- envivioSparkSE (12)
				- ericssonMFMmS (13)"
			SYNTAX INTEGER
				{
				indeterminate(0),
				envivioCommon(1),
				envivioMuseLive(2),
				obsolete1(3),
				obsolete2(4),
				envivio4Manager(5),
				obsolete3(6),
				obsolete4(7),
				obsolete5(8),
				envivio4Balancer(9),
				envivioHalo(10),
				envivioMuseOnDemand(11),
				envivioSparkSE(12),
				ericssonMFMmS(13)
				}

		TcStatusLevel ::= TEXTUAL-CONVENTION
			STATUS current
			DESCRIPTION
				"General equipment status level:
				OK (1)
				Minor (2)
				Major (3)
				Critical (4)"
			SYNTAX INTEGER
				{
				ok(1),
				minor(2),
				major(3),
				critical(4)
				}

		TcUnsigned32 ::= TEXTUAL-CONVENTION
			STATUS current
			DESCRIPTION
				"Unsigned32 code"
			SYNTAX Unsigned32 (0..4294967295)

		TcSeverity ::= TEXTUAL-CONVENTION
			STATUS current
			DESCRIPTION
				"Severity of the alarm:
				- Indeterminate (0)
				- Critical (1)
				- Major (2)
				- Minor (3)
				- Information (4)"
			SYNTAX INTEGER
				{
				indeterminate(0),
				critical(1),
				major(2),
				minor(3),
				information(4)
				}

		TcBoolean ::= TEXTUAL-CONVENTION
			STATUS current
			DESCRIPTION
				"Enumeration of boolean values"
			SYNTAX INTEGER
				{
				false(0),
				true(1)
				}

		TcAlarmState ::= TEXTUAL-CONVENTION
			STATUS current
			DESCRIPTION
				"AlarmState:
				AlarmOff (0)
				AlarmOn (1)
				Event (2)"
			SYNTAX INTEGER
				{
				alarmOff(0),
				alarmOn(1),
				event(2)
				}


--
-- Node definitions
--

		-- 1.3.6.1.4.1.10613.1
		common OBJECT IDENTIFIER ::= { envivio 1 }


		-- 1.3.6.1.4.1.10613.1.1
		sys OBJECT IDENTIFIER ::= { common 1 }

		-- 1.3.6.1.4.1.10613.1.1.1
		name OBJECT-TYPE
			SYNTAX OCTET STRING (SIZE (0..100))
			MAX-ACCESS read-only
			STATUS current
			DESCRIPTION
				"Equipment name"
			::= { sys 1 }

		-- 1.3.6.1.4.1.10613.1.1.2
		description OBJECT-TYPE
			SYNTAX OCTET STRING (SIZE (0..100))
			MAX-ACCESS read-only
			STATUS current
			DESCRIPTION
				"Equipment description"
			::= { sys 2 }

		-- 1.3.6.1.4.1.10613.1.1.3
		serialNumber OBJECT-TYPE
			SYNTAX OCTET STRING (SIZE (0..100))
			MAX-ACCESS read-only
			STATUS current
			DESCRIPTION
				"Equipment serial number"
			::= { sys 3 }

		-- 1.3.6.1.4.1.10613.1.1.4
		currentTime OBJECT-TYPE
			SYNTAX OCTET STRING (SIZE (0..31))
			MAX-ACCESS read-only
			STATUS current
			DESCRIPTION
				"Current time in GMT (YYYY-MM-DDThh:mm:ssZ)"
			::= { sys 4 }

		-- 1.3.6.1.4.1.10613.1.1.5
		upTime OBJECT-TYPE
			SYNTAX TimeTicks
			MAX-ACCESS read-only
			STATUS current
			DESCRIPTION
				"Time since equipment initialization"
			::= { sys 5 }

		-- 1.3.6.1.4.1.10613.1.1.6
		version OBJECT-TYPE
			SYNTAX OCTET STRING (SIZE (0..100))
			MAX-ACCESS read-only
			STATUS current
			DESCRIPTION
				"Equipment version"
			::= { sys 6 }

		-- 1.3.6.1.4.1.10613.1.1.7
		mibVersion OBJECT-TYPE
			SYNTAX OCTET STRING (SIZE (0..100))
			MAX-ACCESS read-only
			STATUS current
			DESCRIPTION
				"MIB version"
			::= { sys 7 }

		-- 1.3.6.1.4.1.10613.1.1.8
		snmpReadWriteCommunity OBJECT-TYPE
			SYNTAX OCTET STRING (SIZE (1..32))
			MAX-ACCESS read-write
			STATUS current
			DESCRIPTION
				"Read-write community name"
			::= { sys 8 }

		-- 1.3.6.1.4.1.10613.1.1.9
		snmpReadCommunity OBJECT-TYPE
			SYNTAX OCTET STRING (SIZE (1..32))
			MAX-ACCESS read-write
			STATUS current
			DESCRIPTION
				"Read community name"
			::= { sys 9 }

		-- 1.3.6.1.4.1.10613.1.1.1000
		sysObjects OBJECT-GROUP
			OBJECTS	{
				name,
				description,
				serialNumber,
				currentTime,
				upTime,
				version,
				mibVersion,
				snmpReadWriteCommunity,
				snmpReadCommunity
			}
			STATUS	current
			DESCRIPTION	"The objects used in the sys section"
			::= { sys 1000 }


		-- 1.3.6.1.4.1.10613.1.2
		general OBJECT IDENTIFIER ::= { common 2 }


		-- 1.3.6.1.4.1.10613.1.2.1
		objectClass OBJECT-TYPE
			SYNTAX TcObjectClass
			MAX-ACCESS read-only
			STATUS current
			DESCRIPTION
				"Identifier indicating the class of the equipment"
			::= { general 1 }


		-- 1.3.6.1.4.1.10613.1.2.2
		objectInstance OBJECT-TYPE
			SYNTAX OCTET STRING (SIZE (0..100))
			MAX-ACCESS read-only
			STATUS current
			DESCRIPTION
				"Identifier indicating the instance of the equipment"
			::= { general 2 }


		-- 1.3.6.1.4.1.10613.1.2.3
		statusLevelId OBJECT-TYPE
			SYNTAX TcStatusLevel
			MAX-ACCESS read-only
			STATUS current
			DESCRIPTION
				"General equipment status level:
				OK (1)
				Minor (2)
				Major (3)
				Critical (4)"
			::= { general 3 }


		-- 1.3.6.1.4.1.10613.1.2.1000
		generalObjects OBJECT-GROUP
			OBJECTS	{
				objectClass,
				objectInstance,
				statusLevelId
			}
			STATUS	current
			DESCRIPTION	"The objects used in the general section"
			::= { general 1000 }


		-- 1.3.6.1.4.1.10613.1.6
		trap OBJECT IDENTIFIER ::= { common 6 }


		-- 1.3.6.1.4.1.10613.1.6.1
		trapAlarmNotification NOTIFICATION-TYPE
			OBJECTS	{
				managedObjectClass,
				managedObjectInstance,
				eventStatus,
				alarmCode,
				eventTime,
				perceivedSeverity,
				additionalText,
				sequenceNumber,
				objectId,
				label,
				alarmId
			}
			STATUS	current
			DESCRIPTION
				"Contains information describing a raised or cleared alarm, or a notification"
			::= { trap 1 }

		-- 1.3.6.1.4.1.10613.1.6.1.1
		managedObjectClass OBJECT-TYPE
			SYNTAX TcObjectClass
			MAX-ACCESS accessible-for-notify
			STATUS current
			DESCRIPTION
				"Identifier indicating the class of the equipment emitting the alarm (or event)"
			::= { trapAlarmNotification 1 }

		-- 1.3.6.1.4.1.10613.1.6.1.2
		managedObjectInstance OBJECT-TYPE
			SYNTAX OCTET STRING (SIZE (0..100))
			MAX-ACCESS accessible-for-notify
			STATUS current
			DESCRIPTION
				"Identifier indicating the instance of the equipment emitting the alarm (or event)"
			::= { trapAlarmNotification 2 }

		-- 1.3.6.1.4.1.10613.1.6.1.3
		eventStatus OBJECT-TYPE
			SYNTAX TcAlarmState
			MAX-ACCESS accessible-for-notify
			STATUS current
			DESCRIPTION
				"Event or status of alarm"
			::= { trapAlarmNotification 3 }

		-- 1.3.6.1.4.1.10613.1.6.1.4
		alarmCode OBJECT-TYPE
			SYNTAX TcUnsigned32
			MAX-ACCESS accessible-for-notify
			STATUS current
			DESCRIPTION
				"DEPRECATED: integer that identifies the type of alarm or event. Must Not be used anymore when developing a new SNMP agent. Use instead alarmId"
			::= { trapAlarmNotification 4 }

		-- 1.3.6.1.4.1.10613.1.6.1.5
		eventTime OBJECT-TYPE
			SYNTAX OCTET STRING (SIZE (0..31))
			MAX-ACCESS accessible-for-notify
			STATUS current
			DESCRIPTION
				"Alarm (or event) time in GMT (YYYY-MM-DDThh:mm:ssZ)"
			::= { trapAlarmNotification 5 }

		-- 1.3.6.1.4.1.10613.1.6.1.6
		perceivedSeverity OBJECT-TYPE
			SYNTAX TcSeverity
			MAX-ACCESS accessible-for-notify
			STATUS current
			DESCRIPTION
				"Severity of the alarm (or event)"
			::= { trapAlarmNotification 6 }

		-- 1.3.6.1.4.1.10613.1.6.1.7
		additionalText OBJECT-TYPE
			SYNTAX OCTET STRING (SIZE (0..511))
			MAX-ACCESS accessible-for-notify
			STATUS current
			DESCRIPTION
				"Text providing additional details about the alarm (or event)"
			::= { trapAlarmNotification 7 }

		-- 1.3.6.1.4.1.10613.1.6.1.8
		sequenceNumber OBJECT-TYPE
			SYNTAX Gauge32
			MAX-ACCESS accessible-for-notify
			STATUS current
			DESCRIPTION
				"Sequence number of the trap (incremented by 1 for each trap emitted)"
			::= { trapAlarmNotification 8 }

		-- 1.3.6.1.4.1.10613.1.6.1.9
		objectId OBJECT-TYPE
			SYNTAX OCTET STRING
			MAX-ACCESS accessible-for-notify
			STATUS current
			DESCRIPTION
				"objectId of the alarm, i.e. the element to which the alarm is related."
			::= { trapAlarmNotification 9 }

		-- 1.3.6.1.4.1.10613.1.6.1.10
		label OBJECT-TYPE
			SYNTAX OCTET STRING
			MAX-ACCESS accessible-for-notify
			STATUS current
			DESCRIPTION
				"Label of the alarm"
			::= { trapAlarmNotification 10 }

		-- 1.3.6.1.4.1.10613.1.6.1.11
		alarmId OBJECT-TYPE
			SYNTAX OCTET STRING
			MAX-ACCESS accessible-for-notify
			STATUS current
			DESCRIPTION
				"String that identifies the type of alarm or event. Must be used instead of alarmCode when developing a new SNMP agent"
			::= { trapAlarmNotification 11 }


		-- 1.3.6.1.4.1.10613.1.6.2
		trapAlarmNotification2 NOTIFICATION-TYPE
			OBJECTS	{
				managedObjectClass2,
				managedObjectInstance2,
				state,
				date,
				severity,
				additionalInfo,
				sequenceNumber2,
				objectId2,
				label2,
				alarmId2,
				failoverTrigger,
				serverId,
				serviceId,
				processingType,
				serverIp
			}
			STATUS	current
			DESCRIPTION
				"Contains information describing a raised or cleared alarm, or a notification"
			::= { trap 2 }

		-- 1.3.6.1.4.1.10613.1.6.2.1
		managedObjectClass2 OBJECT-TYPE
			SYNTAX TcObjectClass
			MAX-ACCESS accessible-for-notify
			STATUS current
			DESCRIPTION
				"Identifier indicating the class of the equipment emitting the alarm (or event)"
			::= { trapAlarmNotification2 1 }

		-- 1.3.6.1.4.1.10613.1.6.2.2
		managedObjectInstance2 OBJECT-TYPE
			SYNTAX OCTET STRING (SIZE (0..100))
			MAX-ACCESS accessible-for-notify
			STATUS current
			DESCRIPTION
				"Identifier indicating the instance of the equipment emitting the alarm (or event)"
			::= { trapAlarmNotification2 2 }

		-- 1.3.6.1.4.1.10613.1.6.2.3
		state OBJECT-TYPE
			SYNTAX TcAlarmState
			MAX-ACCESS accessible-for-notify
			STATUS current
			DESCRIPTION
				"Event or status of alarm"
			::= { trapAlarmNotification2 3 }

		-- 1.3.6.1.4.1.10613.1.6.2.5
		date OBJECT-TYPE
			SYNTAX OCTET STRING (SIZE (0..31))
			MAX-ACCESS accessible-for-notify
			STATUS current
			DESCRIPTION
				"Alarm (or event) time in GMT (YYYY-MM-DDThh:mm:ssZ)"
			::= { trapAlarmNotification2 5 }

		-- 1.3.6.1.4.1.10613.1.6.2.6
		severity OBJECT-TYPE
			SYNTAX TcSeverity
			MAX-ACCESS accessible-for-notify
			STATUS current
			DESCRIPTION
				"Severity of the alarm (or event)"
			::= { trapAlarmNotification2 6 }

		-- 1.3.6.1.4.1.10613.1.6.2.7
		additionalInfo OBJECT-TYPE
			SYNTAX OCTET STRING (SIZE (0..511))
			MAX-ACCESS accessible-for-notify
			STATUS current
			DESCRIPTION
				"Text providing additional details about the alarm (or event)"
			::= { trapAlarmNotification2 7 }

		-- 1.3.6.1.4.1.10613.1.6.2.8
		sequenceNumber2 OBJECT-TYPE
			SYNTAX Gauge32
			MAX-ACCESS accessible-for-notify
			STATUS current
			DESCRIPTION
				"Sequence number of the trap (incremented by 1 for each trap emitted)"
			::= { trapAlarmNotification2 8 }

		-- 1.3.6.1.4.1.10613.1.6.2.9
		objectId2 OBJECT-TYPE
			SYNTAX OCTET STRING
			MAX-ACCESS accessible-for-notify
			STATUS current
			DESCRIPTION
				"objectId of the alarm, i.e. the element to which the alarm is related."
			::= { trapAlarmNotification2 9 }

		-- 1.3.6.1.4.1.10613.1.6.2.10
		label2 OBJECT-TYPE
			SYNTAX OCTET STRING
			MAX-ACCESS accessible-for-notify
			STATUS current
			DESCRIPTION
				"Label of the alarm"
			::= { trapAlarmNotification2 10 }

		-- 1.3.6.1.4.1.10613.1.6.2.11
		alarmId2 OBJECT-TYPE
			SYNTAX OCTET STRING
			MAX-ACCESS accessible-for-notify
			STATUS current
			DESCRIPTION
				"String that identifies the type of alarm or event. Must be used instead of alarmCode when developing a new SNMP agent"
			::= { trapAlarmNotification2 11 }

		-- 1.3.6.1.4.1.10613.1.6.2.12
		failoverTrigger OBJECT-TYPE
			SYNTAX TcBoolean
			MAX-ACCESS accessible-for-notify
			STATUS current
			DESCRIPTION
				"Indicates whether the alarm is configured as a failover trigger"
			::= { trapAlarmNotification2 12 }

		-- 1.3.6.1.4.1.10613.1.6.2.13
		serverId OBJECT-TYPE
			SYNTAX OCTET STRING
			MAX-ACCESS accessible-for-notify
			STATUS current
			DESCRIPTION
				"Server that originally sent this alarm."
			::= { trapAlarmNotification2 13 }

		-- 1.3.6.1.4.1.10613.1.6.2.14
		serviceId OBJECT-TYPE
			SYNTAX OCTET STRING
			MAX-ACCESS accessible-for-notify
			STATUS current
			DESCRIPTION
				"Service in failure when relevant."
			::= { trapAlarmNotification2 14 }

		-- 1.3.6.1.4.1.10613.1.6.2.15
		processingType OBJECT-TYPE
			SYNTAX OCTET STRING
			MAX-ACCESS accessible-for-notify
			STATUS current
			DESCRIPTION
				"Processing type of the process that sent the alarm."
			::= { trapAlarmNotification2 15 }

		-- 1.3.6.1.4.1.10613.1.6.2.16
		serverIp OBJECT-TYPE
			SYNTAX OCTET STRING
			MAX-ACCESS accessible-for-notify
			STATUS current
			DESCRIPTION
				"IP of the Server that originally sent this alarm."
			::= { trapAlarmNotification2 16 }


		-- 1.3.6.1.4.1.10613.1.6.100
		notifications NOTIFICATION-GROUP
			NOTIFICATIONS	{
				trapAlarmNotification,
				trapAlarmNotification2
			}
			STATUS		current
			DESCRIPTION	"Notifications"
			::= { trap 100 }


		-- 1.3.6.1.4.1.10613.1.6.101
		trapAlarmNotificationObjects OBJECT-GROUP
			OBJECTS	{
				managedObjectClass,
				managedObjectInstance,
				eventStatus,
				alarmCode,
				eventTime,
				perceivedSeverity,
				additionalText,
				sequenceNumber,
				objectId,
				label,
				alarmId
			}
			STATUS	current
			DESCRIPTION	"The objects used in trapAlarmNotification"
			::= { trap 101 }


		-- 1.3.6.1.4.1.10613.1.6.102
		trapAlarmNotification2Objects OBJECT-GROUP
			OBJECTS	{
				managedObjectClass2,
				managedObjectInstance2,
				state,
				date,
				severity,
				additionalInfo,
				sequenceNumber2,
				objectId2,
				label2,
				alarmId2,
				failoverTrigger,
				serverId,
				serviceId,
				processingType,
				serverIp
			}
			STATUS	current
			DESCRIPTION	"The objects used in trapAlarmNotification2"
			::= { trap 102 }

	END

--
-- ENVIVIO-COMMON-MIB.mib
--
